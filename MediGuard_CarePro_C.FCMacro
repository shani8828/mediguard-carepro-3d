# Generated by make_screen.py: 320x240 TFT screen layout as merged pixel rectangles
# rect = (col0, row0, col1, row1) end-exclusive, row 0 = top of screen
UI_PX = (320, 240)
UI_LAYERS = [{'color': (0.11, 0.2, 0.34), 'level': 0, 'name': 'Screen_Status_Bar', 'rects': [(0, 0, 320, 32)]},
 {'color': (0.11, 0.2, 0.34), 'level': 0, 'name': 'Screen_Dividers', 'rects': [(12, 168, 308, 170), (215, 178, 217, 231)]},
 {'color': (0.98, 0.7, 0.16),
  'level': 0,
  'name': 'Screen_TimeOfDay_Chip',
  'rects': [(21, 42, 186, 43), (19, 43, 188, 44), (17, 44, 190, 45), (16, 45, 191, 46), (15, 46, 192, 47), (14, 47, 193, 49), (13, 49, 194, 51), (12, 51, 195, 60), (13, 60, 194, 62),
            (14, 62, 193, 64), (15, 64, 192, 65), (16, 65, 191, 66), (17, 66, 190, 67), (19, 67, 188, 68), (21, 68, 186, 69)]},
 {'color': (0.62, 0.7, 0.78),
  'level': 1,
  'name': 'Screen_Date',
  'rects': [(58, 10, 65, 11), (123, 10, 127, 11), (104, 10, 108, 11), (12, 10, 21, 11), (74, 10, 79, 11), (49, 10, 53, 11), (133, 10, 137, 11), (114, 10, 118, 11), (73, 11, 75, 12), (48, 11, 50, 12),
            (122, 11, 124, 12), (137, 11, 138, 12), (113, 11, 115, 12), (117, 11, 119, 12), (79, 11, 81, 12), (132, 11, 134, 12), (103, 11, 105, 12), (92, 11, 94, 13), (63, 11, 65, 13),
            (132, 12, 133, 13), (48, 12, 49, 13), (103, 12, 104, 13), (80, 12, 81, 13), (122, 12, 123, 13), (118, 12, 119, 14), (131, 13, 133, 14), (91, 13, 97, 14), (31, 13, 35, 14),
            (86, 13, 90, 14), (127, 11, 129, 15), (53, 11, 55, 15), (108, 11, 110, 15), (62, 13, 64, 15), (131, 14, 137, 15), (34, 14, 36, 15), (30, 14, 32, 15), (85, 14, 87, 15), (89, 14, 90, 15),
            (131, 15, 134, 16), (52, 15, 54, 16), (107, 15, 109, 16), (126, 15, 128, 16), (62, 15, 63, 16), (136, 15, 138, 16), (84, 15, 86, 16), (29, 15, 31, 16), (118, 14, 120, 17),
            (35, 15, 36, 17), (106, 16, 108, 17), (51, 16, 53, 17), (137, 16, 138, 17), (125, 16, 127, 17), (29, 16, 30, 17), (80, 13, 82, 18), (84, 16, 85, 18), (61, 16, 63, 18), (137, 17, 139, 18),
            (50, 17, 52, 18), (105, 17, 107, 18), (29, 17, 36, 18), (124, 17, 126, 18), (112, 12, 114, 19), (72, 12, 74, 19), (26, 13, 27, 19), (20, 13, 22, 19), (131, 16, 133, 19),
            (118, 17, 119, 19), (61, 18, 62, 19), (137, 18, 138, 19), (104, 18, 106, 19), (80, 18, 81, 19), (49, 18, 51, 19), (123, 18, 125, 19), (84, 18, 86, 19), (29, 18, 30, 19), (92, 14, 94, 20),
            (73, 19, 75, 20), (35, 19, 36, 20), (21, 19, 22, 20), (79, 19, 81, 20), (103, 19, 105, 20), (48, 19, 50, 20), (122, 19, 124, 20), (117, 19, 119, 20), (136, 19, 138, 20), (25, 19, 27, 20),
            (113, 19, 115, 20), (89, 19, 90, 20), (132, 19, 134, 20), (85, 19, 86, 20), (30, 19, 31, 20), (16, 11, 17, 21), (60, 19, 62, 21), (40, 19, 41, 21), (26, 20, 27, 21), (103, 20, 110, 21),
            (21, 20, 25, 21), (48, 20, 55, 21), (93, 20, 97, 21), (31, 20, 35, 21), (86, 20, 90, 21), (122, 20, 129, 21), (74, 20, 79, 21), (133, 20, 137, 21), (114, 20, 118, 21), (39, 21, 41, 22),
            (39, 22, 40, 23)]},
 {'color': (0.97, 0.97, 0.97),
  'level': 1,
  'name': 'Screen_Time',
  'rects': [(229, 9, 235, 10), (217, 9, 222, 10), (293, 9, 297, 10), (262, 9, 267, 10), (282, 9, 286, 10), (249, 9, 254, 10), (303, 9, 307, 10), (247, 10, 255, 11), (260, 10, 268, 11),
            (228, 10, 237, 11), (215, 10, 223, 11), (302, 10, 307, 12), (293, 10, 298, 12), (252, 11, 256, 12), (215, 11, 218, 12), (247, 11, 250, 12), (260, 11, 263, 12), (220, 11, 224, 12),
            (233, 11, 237, 12), (265, 11, 269, 12), (281, 10, 287, 13), (227, 11, 231, 13), (234, 12, 237, 13), (246, 12, 250, 13), (259, 12, 263, 13), (253, 12, 256, 13), (221, 12, 224, 13),
            (214, 12, 218, 13), (266, 12, 269, 13), (301, 12, 307, 14), (293, 12, 299, 14), (284, 13, 288, 14), (228, 13, 231, 14), (233, 13, 237, 14), (240, 12, 243, 15), (280, 13, 283, 15),
            (229, 14, 236, 15), (297, 14, 303, 16), (285, 14, 288, 16), (228, 15, 236, 16), (279, 15, 283, 16), (286, 16, 289, 17), (279, 16, 282, 17), (227, 16, 231, 17), (233, 16, 237, 17),
            (214, 13, 217, 18), (221, 13, 225, 18), (253, 13, 257, 18), (266, 13, 270, 18), (246, 13, 249, 18), (259, 13, 262, 18), (298, 16, 302, 18), (279, 17, 289, 18), (234, 17, 237, 19),
            (227, 17, 230, 19), (278, 18, 290, 19), (246, 18, 250, 19), (259, 18, 263, 19), (253, 18, 256, 19), (221, 18, 224, 19), (214, 18, 218, 19), (299, 18, 301, 19), (266, 18, 269, 19),
            (252, 19, 256, 20), (215, 19, 218, 20), (247, 19, 250, 20), (227, 19, 231, 20), (260, 19, 263, 20), (220, 19, 224, 20), (233, 19, 237, 20), (265, 19, 269, 20), (278, 19, 281, 21),
            (287, 19, 290, 21), (247, 20, 255, 21), (260, 20, 268, 21), (228, 20, 237, 21), (215, 20, 223, 21), (293, 14, 296, 22), (304, 14, 307, 22), (240, 19, 243, 22), (229, 21, 235, 22),
            (217, 21, 222, 22), (262, 21, 267, 22), (249, 21, 254, 22), (287, 21, 291, 22), (277, 21, 281, 22)]},
 {'color': (0.06, 0.1, 0.18),
  'level': 1,
  'name': 'Screen_TimeOfDay_Text',
  'rects': [(26, 45, 28, 47), (20, 46, 21, 47), (34, 47, 35, 48), (19, 47, 22, 48), (27, 47, 29, 49), (20, 48, 23, 49), (33, 48, 36, 49), (32, 49, 35, 50), (21, 49, 24, 50), (31, 50, 34, 51),
            (45, 50, 49, 51), (132, 50, 140, 51), (148, 50, 153, 51), (54, 50, 58, 51), (22, 50, 23, 51), (73, 50, 80, 51), (118, 50, 125, 51), (160, 50, 166, 51), (168, 50, 176, 51),
            (63, 50, 68, 51), (84, 50, 88, 52), (102, 50, 106, 52), (61, 51, 64, 52), (116, 51, 119, 52), (32, 51, 33, 52), (165, 51, 166, 52), (27, 51, 30, 52), (146, 51, 149, 52), (78, 51, 81, 52),
            (159, 51, 161, 52), (138, 51, 141, 52), (123, 51, 125, 52), (67, 51, 70, 53), (53, 51, 58, 53), (152, 51, 155, 53), (45, 51, 50, 54), (25, 52, 32, 54), (139, 52, 142, 54),
            (158, 52, 161, 54), (102, 52, 107, 54), (84, 52, 89, 54), (52, 53, 58, 54), (168, 51, 171, 55), (79, 52, 82, 55), (84, 54, 90, 55), (52, 54, 54, 55), (49, 54, 51, 55), (158, 54, 165, 55),
            (102, 54, 108, 55), (91, 50, 94, 56), (109, 50, 112, 56), (73, 51, 76, 56), (18, 54, 22, 56), (106, 55, 108, 56), (159, 55, 166, 56), (88, 55, 90, 56), (168, 55, 176, 56),
            (78, 55, 81, 56), (49, 55, 54, 56), (121, 55, 125, 56), (24, 54, 33, 57), (140, 54, 143, 57), (35, 55, 39, 57), (49, 56, 53, 57), (160, 56, 167, 57), (73, 56, 80, 57), (153, 53, 156, 58),
            (68, 53, 71, 58), (107, 56, 112, 58), (89, 56, 94, 58), (163, 57, 167, 58), (78, 57, 81, 58), (145, 52, 148, 59), (60, 52, 63, 59), (115, 52, 118, 59), (25, 57, 32, 59),
            (139, 57, 142, 59), (50, 57, 53, 59), (164, 58, 167, 59), (23, 58, 24, 59), (79, 58, 82, 59), (132, 51, 135, 60), (122, 56, 125, 60), (168, 56, 171, 60), (90, 58, 94, 60),
            (108, 58, 112, 60), (67, 58, 70, 60), (152, 58, 155, 60), (61, 59, 64, 60), (116, 59, 119, 60), (163, 59, 166, 60), (22, 59, 25, 60), (27, 59, 30, 60), (158, 59, 160, 60),
            (79, 59, 83, 60), (33, 59, 34, 60), (146, 59, 149, 60), (138, 59, 141, 60), (97, 50, 100, 61), (45, 54, 48, 61), (55, 54, 58, 61), (84, 55, 87, 61), (102, 55, 105, 61), (73, 57, 76, 61),
            (132, 60, 140, 61), (148, 60, 153, 61), (168, 60, 176, 61), (91, 60, 94, 61), (109, 60, 112, 61), (118, 60, 125, 61), (32, 60, 35, 61), (21, 60, 24, 61), (80, 60, 83, 61),
            (63, 60, 68, 61), (158, 60, 165, 61), (20, 61, 23, 62), (33, 61, 36, 62), (34, 62, 37, 63), (21, 62, 22, 63), (35, 63, 36, 64), (28, 62, 30, 66)]},
 {'color': (0.97, 0.97, 0.97),
  'level': 1,
  'name': 'Screen_Medicine_Name',
  'rects': [(116, 84, 127, 85), (114, 85, 127, 86), (41, 85, 52, 87), (16, 85, 27, 87), (113, 86, 127, 87), (40, 87, 52, 89), (16, 87, 28, 89), (112, 87, 127, 89), (228, 84, 235, 90),
            (112, 89, 120, 91), (39, 89, 52, 91), (16, 89, 29, 92), (90, 86, 98, 93), (112, 91, 119, 93), (194, 92, 200, 93), (172, 92, 177, 93), (209, 92, 215, 93), (255, 92, 262, 93),
            (137, 92, 146, 93), (67, 92, 75, 93), (38, 91, 52, 94), (16, 92, 30, 94), (207, 93, 217, 94), (253, 93, 264, 94), (64, 93, 78, 94), (192, 93, 202, 94), (134, 93, 148, 94),
            (170, 93, 178, 94), (182, 93, 189, 95), (243, 93, 250, 95), (191, 94, 203, 95), (169, 94, 178, 95), (252, 94, 265, 95), (132, 94, 150, 95), (16, 94, 31, 95), (206, 94, 218, 95),
            (62, 94, 79, 95), (37, 94, 52, 95), (160, 93, 167, 96), (168, 95, 178, 96), (182, 95, 203, 96), (243, 95, 265, 96), (61, 95, 80, 96), (25, 95, 31, 96), (131, 95, 151, 96),
            (37, 95, 43, 96), (205, 95, 219, 96), (36, 96, 43, 97), (182, 96, 219, 97), (60, 96, 81, 97), (130, 96, 152, 97), (25, 96, 32, 98), (243, 96, 266, 98), (160, 96, 178, 98),
            (60, 97, 69, 98), (36, 97, 42, 98), (130, 97, 153, 98), (73, 97, 82, 98), (182, 97, 220, 98), (108, 93, 126, 99), (87, 93, 106, 99), (160, 98, 171, 99), (143, 98, 153, 99),
            (129, 98, 139, 99), (35, 98, 42, 99), (243, 98, 254, 99), (257, 98, 267, 99), (26, 98, 32, 99), (75, 98, 82, 99), (182, 98, 192, 99), (196, 98, 208, 99), (176, 98, 178, 99),
            (211, 98, 220, 99), (59, 98, 67, 100), (243, 99, 252, 100), (26, 99, 33, 100), (75, 99, 83, 100), (258, 99, 267, 100), (129, 99, 138, 100), (160, 99, 170, 100), (182, 99, 191, 100),
            (212, 99, 220, 101), (197, 99, 206, 101), (145, 99, 154, 101), (35, 99, 41, 101), (27, 100, 33, 101), (160, 100, 169, 101), (128, 100, 137, 101), (76, 100, 83, 102), (58, 100, 66, 102),
            (27, 101, 41, 102), (182, 100, 190, 104), (243, 100, 251, 104), (28, 102, 40, 104), (160, 101, 168, 105), (28, 104, 39, 105), (29, 105, 39, 106), (58, 102, 84, 107), (29, 106, 38, 107),
            (128, 101, 136, 108), (146, 101, 154, 108), (30, 107, 38, 109), (58, 107, 66, 109), (128, 108, 137, 109), (90, 99, 98, 110), (145, 108, 154, 110), (59, 109, 67, 110), (129, 109, 138, 110),
            (81, 109, 83, 110), (31, 109, 37, 111), (143, 110, 153, 111), (129, 110, 139, 111), (90, 110, 99, 111), (79, 110, 83, 111), (59, 110, 68, 111), (60, 111, 69, 112), (130, 111, 153, 112),
            (76, 111, 83, 112), (60, 112, 83, 113), (130, 112, 152, 113), (91, 111, 105, 114), (61, 113, 83, 114), (131, 113, 151, 114), (132, 114, 150, 115), (62, 114, 83, 115), (92, 114, 105, 115),
            (134, 115, 148, 116), (64, 115, 81, 116), (93, 115, 105, 116), (228, 93, 235, 117), (44, 95, 52, 117), (16, 95, 24, 117), (112, 99, 119, 117), (259, 100, 267, 117), (213, 101, 220, 117),
            (197, 101, 205, 117), (182, 104, 189, 117), (243, 104, 250, 117), (160, 105, 167, 117), (67, 116, 77, 117), (95, 116, 105, 117), (137, 116, 146, 117)]},
 {'color': (0.62, 0.7, 0.78),
  'level': 1,
  'name': 'Screen_Medicine_Strength',
  'rects': [(42, 136, 46, 137), (30, 136, 34, 137), (16, 136, 23, 138), (29, 137, 35, 138), (41, 137, 47, 138), (40, 138, 43, 139), (33, 138, 36, 139), (45, 138, 48, 139), (28, 138, 31, 139),
            (95, 137, 97, 140), (143, 137, 145, 140), (34, 139, 36, 140), (40, 139, 42, 140), (46, 139, 48, 140), (28, 139, 30, 140), (114, 136, 116, 141), (16, 138, 18, 141), (103, 140, 108, 141),
            (61, 140, 65, 141), (68, 140, 71, 141), (117, 140, 121, 141), (133, 140, 137, 141), (78, 140, 82, 141), (58, 140, 60, 141), (84, 140, 85, 141), (93, 140, 100, 142), (141, 140, 148, 142),
            (58, 141, 72, 142), (77, 141, 85, 142), (16, 141, 22, 142), (131, 141, 139, 142), (114, 141, 122, 142), (102, 141, 109, 142), (137, 142, 139, 143), (70, 142, 73, 143), (76, 142, 79, 143),
            (58, 142, 61, 143), (114, 142, 117, 143), (131, 142, 133, 143), (102, 142, 103, 143), (82, 142, 85, 143), (108, 142, 110, 143), (16, 142, 23, 143), (120, 142, 123, 143),
            (64, 142, 67, 144), (138, 143, 140, 144), (21, 143, 24, 144), (130, 143, 132, 144), (103, 143, 110, 144), (16, 143, 17, 144), (102, 144, 110, 145), (47, 140, 49, 146), (27, 140, 29, 146),
            (35, 140, 37, 146), (39, 140, 41, 146), (130, 144, 140, 146), (101, 145, 104, 146), (83, 143, 85, 147), (121, 143, 123, 147), (76, 143, 78, 147), (114, 143, 116, 147), (22, 144, 24, 147),
            (108, 145, 110, 147), (130, 146, 132, 147), (34, 146, 36, 147), (40, 146, 42, 147), (46, 146, 48, 147), (28, 146, 30, 147), (143, 142, 145, 148), (95, 142, 97, 148), (101, 146, 103, 148),
            (33, 147, 36, 148), (107, 147, 110, 148), (76, 147, 79, 148), (15, 147, 17, 148), (21, 147, 24, 148), (40, 147, 43, 148), (138, 147, 139, 148), (114, 147, 117, 148), (131, 147, 133, 148),
            (45, 147, 48, 148), (82, 147, 85, 148), (28, 147, 31, 148), (120, 147, 123, 148), (102, 148, 110, 149), (77, 148, 85, 149), (15, 148, 23, 149), (95, 148, 100, 149), (131, 148, 139, 149),
            (29, 148, 35, 149), (114, 148, 122, 149), (143, 148, 148, 149), (41, 148, 47, 149), (126, 136, 128, 150), (71, 143, 73, 150), (58, 143, 60, 150), (64, 144, 66, 150), (103, 149, 107, 150),
            (144, 149, 148, 150), (30, 149, 34, 150), (133, 149, 138, 150), (96, 149, 100, 150), (17, 149, 22, 150), (114, 149, 116, 150), (78, 149, 82, 150), (108, 149, 110, 150),
            (117, 149, 121, 150), (42, 149, 46, 150), (83, 149, 85, 151), (82, 151, 85, 152), (77, 151, 78, 152), (77, 152, 84, 153), (78, 153, 83, 154)]},
 {'color': (0.62, 0.7, 0.78),
  'level': 1,
  'name': 'Screen_Labels',
  'rects': [(15, 181, 21, 182), (29, 181, 33, 182), (242, 181, 248, 182), (40, 181, 45, 182), (261, 181, 264, 182), (254, 181, 257, 182), (277, 181, 283, 182), (286, 181, 292, 182),
            (50, 181, 56, 182), (272, 181, 274, 182), (231, 181, 237, 182), (254, 182, 258, 183), (271, 182, 274, 183), (27, 182, 30, 183), (44, 182, 45, 183), (236, 182, 238, 183),
            (290, 182, 293, 183), (32, 182, 35, 183), (246, 182, 249, 183), (20, 182, 22, 183), (266, 181, 269, 184), (39, 182, 41, 184), (291, 183, 293, 184), (33, 183, 35, 184),
            (247, 183, 249, 184), (253, 183, 258, 184), (262, 182, 264, 185), (50, 182, 52, 185), (242, 182, 244, 185), (277, 182, 279, 185), (286, 182, 288, 185), (266, 184, 267, 185),
            (246, 184, 249, 185), (256, 184, 258, 185), (39, 184, 43, 185), (290, 184, 293, 185), (271, 183, 273, 186), (253, 184, 255, 186), (268, 184, 270, 186), (256, 185, 259, 186),
            (262, 185, 267, 186), (242, 185, 248, 186), (277, 185, 283, 186), (286, 185, 292, 186), (39, 185, 45, 186), (50, 185, 56, 186), (33, 184, 36, 187), (257, 186, 259, 187),
            (252, 186, 255, 187), (41, 186, 46, 187), (268, 186, 273, 187), (290, 186, 293, 187), (246, 186, 249, 187), (27, 183, 29, 188), (237, 183, 239, 188), (21, 183, 23, 188),
            (263, 186, 267, 188), (252, 187, 259, 188), (33, 187, 35, 188), (15, 182, 17, 189), (231, 182, 233, 189), (50, 186, 52, 189), (277, 186, 279, 189), (291, 187, 293, 189),
            (43, 187, 46, 189), (247, 187, 249, 189), (27, 188, 30, 189), (39, 188, 40, 189), (236, 188, 238, 189), (252, 188, 254, 189), (32, 188, 35, 189), (257, 188, 260, 189), (20, 188, 22, 189),
            (242, 186, 244, 190), (286, 186, 288, 190), (269, 187, 272, 190), (263, 188, 266, 190), (15, 189, 21, 190), (251, 189, 254, 190), (291, 189, 294, 190), (258, 189, 260, 190),
            (277, 189, 283, 190), (247, 189, 250, 190), (39, 189, 45, 190), (50, 189, 56, 190), (29, 189, 34, 190), (231, 189, 237, 190)]},
 {'color': (0.35, 0.85, 0.5),
  'level': 1,
  'name': 'Screen_Dose',
  'rects': [(20, 202, 28, 203), (45, 202, 65, 206), (17, 203, 28, 206), (17, 206, 20, 207), (137, 203, 142, 208), (65, 208, 76, 209), (93, 208, 98, 209), (121, 208, 128, 209), (84, 201, 90, 210),
            (119, 209, 130, 210), (65, 209, 78, 210), (91, 209, 99, 210), (134, 208, 148, 211), (65, 210, 79, 211), (84, 210, 100, 211), (117, 210, 131, 211), (95, 211, 101, 212),
            (116, 211, 123, 212), (126, 211, 132, 212), (65, 211, 67, 212), (84, 211, 92, 212), (74, 211, 80, 213), (84, 212, 91, 213), (116, 212, 122, 213), (127, 212, 132, 214), (96, 212, 102, 214),
            (67, 213, 80, 214), (116, 213, 121, 214), (127, 214, 133, 215), (115, 214, 121, 215), (65, 214, 80, 215), (64, 215, 80, 216), (75, 216, 80, 217), (64, 216, 70, 217), (97, 214, 102, 218),
            (115, 215, 133, 218), (84, 213, 90, 219), (22, 206, 28, 220), (137, 211, 142, 220), (74, 217, 80, 220), (63, 217, 69, 220), (116, 218, 121, 220), (96, 218, 102, 220), (84, 219, 91, 220),
            (131, 219, 132, 220), (116, 220, 123, 221), (128, 220, 132, 221), (73, 220, 80, 221), (64, 220, 70, 221), (137, 220, 143, 221), (84, 220, 92, 221), (95, 220, 101, 221),
            (117, 221, 132, 222), (84, 221, 100, 222), (137, 221, 147, 222), (64, 221, 80, 222), (119, 222, 132, 223), (138, 222, 147, 223), (91, 222, 99, 223), (65, 222, 73, 223),
            (106, 201, 112, 224), (52, 206, 58, 224), (17, 220, 33, 224), (75, 222, 80, 224), (84, 222, 90, 224), (93, 223, 98, 224), (139, 223, 147, 224), (121, 223, 130, 224), (66, 223, 72, 224)]},
 {'color': (0.97, 0.97, 0.97),
  'level': 1,
  'name': 'Screen_Drawer_No',
  'rects': [(235, 202, 244, 203), (233, 203, 246, 204), (233, 204, 247, 205), (233, 205, 248, 206), (233, 206, 235, 207), (241, 206, 248, 207), (242, 207, 248, 210), (241, 210, 247, 211),
            (236, 211, 246, 212), (236, 212, 245, 213), (236, 213, 246, 214), (236, 214, 248, 215), (241, 215, 248, 216), (242, 216, 248, 217), (243, 217, 249, 218), (242, 218, 248, 219),
            (232, 218, 233, 219), (232, 219, 235, 220), (241, 219, 248, 220), (232, 220, 248, 221), (232, 221, 247, 222), (233, 222, 246, 223), (235, 223, 244, 224)]}]

# MediGuard Care-Pro Concept C - geometry definition (single source of truth)
# Units: mm.  X = width (left -80 .. right +80), Y = depth (front face 0 .. rear 200),
# Z = height (0 .. 250).  Drawer #3 is shown extended 70 mm (front at Y = -70).
#
# Assumptions taken where the sketches disagree:
#   8 drawers on a 22 mm pitch (stack Z 20..196), 2 mm gap between 20 mm fronts
#   header slant follows 70 mm depth x 54 mm height (~37.6 deg), not 30 deg
#   timing-belt pulleys 165 mm centre-to-centre, closed depth 200 mm
import math

try:                      # inside the FreeCAD macro the screen data is pasted above this file
    UI_LAYERS
except NameError:
    from screen_ui import UI_LAYERS, UI_PX

W, D, H = 160.0, 200.0, 250.0
BASE_H = 20.0
STACK_Z0, STACK_Z1 = 20.0, 196.0
PITCH, FRONT_H = 22.0, 20.0
N_DRAWERS = 8
EXT_DRAWER = 2          # index 0 = bottom; drawer #3 from bottom is extended
EXT = 70.0
WALL = 3.0
SLANT_D = 70.0
HDR_H = H - STACK_Z1    # 54
SLANT_ANG = math.degrees(math.atan2(HDR_H, SLANT_D))
SLANT_LEN = math.hypot(SLANT_D, HDR_H)
NY, NZ = -HDR_H / SLANT_LEN, SLANT_D / SLANT_LEN   # outward normal of slanted face

COL = {
    "shell": (0.93, 0.93, 0.90), "shell2": (0.85, 0.86, 0.84), "front": (0.97, 0.97, 0.95),
    "dark": (0.18, 0.19, 0.21), "screen": (0.04, 0.09, 0.17), "rubber": (0.12, 0.12, 0.12),
    "metal": (0.70, 0.72, 0.75), "brass": (0.80, 0.65, 0.30), "led": (0.20, 0.85, 0.35),
    "pcb": (0.10, 0.50, 0.25), "batt": (0.20, 0.35, 0.70), "belt": (0.15, 0.15, 0.15),
    "spring": (0.75, 0.75, 0.80), "blister": (0.80, 0.85, 0.90), "foil": (0.75, 0.77, 0.80),
    "accent": (0.95, 0.55, 0.15), "red": (0.85, 0.20, 0.20), "tray": (0.80, 0.83, 0.86),
}

parts = []


def add(name, group, color, prim, transforms=None, cut=False):
    """prim: ('box', x0,y0,z0,x1,y1,z1) | ('cyl', r, h, (bx,by,bz), (dx,dy,dz))
             ('tube', ri, ro, h, base, dir) | ('prismx', x0, x1, [(y,z),...])
             ('dome', r, centre, dir) | ('torus', R, r, centre, dir)
             ('rects', [(x0,y0,x1,y1),...], z0, z1)  many flat boxes (screen pixels)
       transforms: list of ('rot', (ax,ay,az), deg) [about origin] or ('move', (x,y,z))
       cut=True -> hidden in the cut-away preview (right wall, roof ...)"""
    parts.append(dict(name=name, group=group, color=COL.get(color, color) if isinstance(color, str) else tuple(color), prim=prim,
                      tf=transforms or [], cut=cut))


def on_slant(u, x, off, thick, sx, su, name, group, color, prim="box", r=None):
    """Place a feature on the slanted header face. u = distance along slope from front edge."""
    py, pz = u * SLANT_D / SLANT_LEN, STACK_Z1 + u * HDR_H / SLANT_LEN
    cy, cz = py + NY * off, pz + NZ * off
    tf = [("rot", (1, 0, 0), SLANT_ANG), ("move", (x, cy, cz))]
    if prim == "box":
        add(name, group, color, ("box", -sx / 2, -su / 2, -thick / 2, sx / 2, su / 2, thick / 2), tf)
    else:
        add(name, group, color, ("cyl", r, thick, (0, 0, -thick / 2), (0, 0, 1)), tf)


SCREEN_W, SCREEN_H, SCREEN_X, SCREEN_OFF = 58.0, 43.0, -36.0, 2.4   # active area, top surface


def screen_ui():
    """Raised screen graphics: each colour layer of the 320x240 layout becomes one part."""
    u = SLANT_LEN / 2
    cy = u * SLANT_D / SLANT_LEN + NY * SCREEN_OFF
    cz = STACK_Z1 + u * HDR_H / SLANT_LEN + NZ * SCREEN_OFF
    tf = [("rot", (1, 0, 0), SLANT_ANG), ("move", (SCREEN_X, cy, cz))]
    px, py = SCREEN_W / UI_PX[0], SCREEN_H / UI_PX[1]
    for L in UI_LAYERS:
        z0 = 0.04 * L["level"]
        rs = [(-SCREEN_W / 2 + c0 * px, SCREEN_H / 2 - r1 * py, -SCREEN_W / 2 + c1 * px, SCREEN_H / 2 - r0 * py)
              for c0, r0, c1, r1 in L["rects"]]
        add(L["name"], "Display_Screen", L["color"], ("rects", rs, z0, z0 + 0.04), tf)


def rounded_profile():
    pts = [(0, 20), (D, 20)]
    R = 10.0
    for i in range(0, 7):                       # rear-top corner R10
        a = math.radians(90 * i / 6)
        pts.append((D - R + R * math.cos(a), H - R + R * math.sin(a)))
    pts += [(SLANT_D, H), (0, STACK_Z1)]
    return pts


def drawer_z(i):
    return STACK_Z0 + PITCH * i + 1.0


def build():
    parts.clear()
    xi = W / 2 - WALL   # 77 inner face of side walls

    # ---------------- HOUSING ----------------
    prof = rounded_profile()
    add("Wall_Left", "Housing", "shell", ("prismx", -W / 2, -xi, prof))
    add("Wall_Right", "Housing", "shell", ("prismx", xi, W / 2, prof), cut=True)
    add("Back_Wall", "Housing", "shell", ("box", -xi, D - 5, 20, xi, D, H - 10))
    add("Back_Corner_Round", "Housing", "shell", ("cyl", 10, 2 * xi, (-xi, D - 10, H - 10), (1, 0, 0)), cut=True)
    add("Roof_Flat", "Housing", "shell", ("box", -xi, SLANT_D, H - WALL, xi, D - 10, H), cut=True)
    p1, p2 = (0, STACK_Z1), (SLANT_D, H)
    poly = [p1, p2, (p2[0] - NY * WALL, p2[1] - NZ * WALL), (p1[0] - NY * WALL, p1[1] - NZ * WALL)]
    add("Header_Slanted_Panel", "Housing", "shell2", ("prismx", -xi, xi, poly))
    add("Header_Front_Rail", "Housing", "shell2", ("box", -xi, 0, STACK_Z1 - 3, xi, 5, STACK_Z1))
    add("Header_Inner_Deck", "Housing", "shell2", ("box", -xi, 5, STACK_Z1 - 4, xi, 160, STACK_Z1 - 2), cut=True)
    add("Floor_Plate", "Housing", "shell2", ("box", -xi, 0, 18, xi, D - 5, 20))
    add("Stile_Left", "Housing", "front", ("box", -xi, 0, STACK_Z0, -68, 5, STACK_Z1 - 3))
    add("Stile_Right_LockPanel", "Housing", "front", ("box", 68, 0, STACK_Z0, xi, 5, STACK_Z1 - 3))
    add("Partition_Rear_L", "Housing", "shell2", ("box", -xi, 160, 20, 38, 163, STACK_Z1 - 2))
    add("Partition_Rear_R", "Housing", "shell2", ("box", 62, 160, 20, xi, 163, STACK_Z1 - 2), cut=True)
    # plinth base (hollow) + rubber feet
    add("Plinth_Bottom", "Base", "shell2", ("box", -78, 3, 3, 78, 197, 5))
    add("Plinth_Front", "Base", "shell", ("box", -78, 3, 5, 78, 5, 18))
    add("Plinth_Back", "Base", "shell", ("box", -78, 195, 5, 78, 197, 18))
    add("Plinth_Left", "Base", "shell", ("box", -78, 5, 5, -76, 195, 18))
    add("Plinth_Right", "Base", "shell", ("box", 76, 5, 5, 78, 195, 18), cut=True)
    for i, (fx, fy) in enumerate([(-66, 15), (66, 15), (-66, 185), (66, 185)]):
        add(f"Rubber_Foot_{i+1}", "Base", "rubber", ("cyl", 7, 3, (fx, fy, 0), (0, 0, 1)))

    # ---------------- HEADER: display + speaker ----------------
    on_slant(SLANT_LEN / 2, -36, 1.0, 2.0, 72, 52, "Display_Module_Bezel", "Header", "dark")
    on_slant(SLANT_LEN / 2, -36, 2.2, 0.4, 58, 43, "Display_Active_Screen", "Header", "screen")
    screen_ui()
    on_slant(SLANT_LEN / 2, 40, 0.75, 1.5, 0, 0, "Speaker_Grille", "Header", "dark", "cyl", 21)
    for k in range(-3, 4):
        on_slant(SLANT_LEN / 2 + k * 5, 40, 1.7, 0.4, 30 - abs(k) * 3.5, 2.2,
                 f"Speaker_Slot_{k+4}", "Header", "shell2")
    # right side ports & reset, antenna
    add("USB_C_DC_Port", "Ports", "dark", ("box", W / 2, 180, 12, W / 2 + 0.6, 190, 18), cut=True)
    add("Reset_Button", "Ports", "accent", ("cyl", 4, 0.8, (W / 2, 185, 40), (1, 0, 0)), cut=True)
    add("GSM_Antenna_Base", "Ports", "dark", ("cyl", 5, 4, (64, 192, H), (0, 0, 1)))
    add("GSM_Antenna_Mast", "Ports", "dark", ("cyl", 3, 45, (64, 192, H + 4), (0, 0, 1)))

    # ---------------- DRAWERS ----------------
    for i in range(N_DRAWERS):
        z0 = drawer_z(i)
        dy = -EXT if i == EXT_DRAWER else 0.0
        g = f"Drawer_{i+1}"
        mv = [("move", (0, dy, 0))] if dy else []
        add(f"D{i+1}_Front", g, "front", ("box", -68, 0, z0, 68, 5, z0 + FRONT_H), mv)
        add(f"D{i+1}_Finger_Pull", g, "dark", ("box", -25, -0.5, z0 + 6, 25, 0.2, z0 + 14), mv)
        for k, lx in enumerate((-60, -54, -48)):
            add(f"D{i+1}_LED_{k+1}", g, "led" if k <= i % 3 else "dark",
                ("cyl", 1.5, 0.8, (lx, 0.2, z0 + 15), (0, -1, 0)), mv)
        add(f"D{i+1}_Meal_Icon", g, "accent", ("box", -57, -0.4, z0 + 4, -51, 0.2, z0 + 9), mv)
        add(f"D{i+1}_Popper_Dock", g, "shell2", ("box", 38, -0.6, z0 + 2, 64, 0.2, z0 + 18), mv)
        add(f"D{i+1}_Override_Pin", g, "dark", ("cyl", 1.25, 0.8, (32, 0.2, z0 + 5), (0, -1, 0)), mv)
        # tray body
        add(f"D{i+1}_Tray_Floor", g, "tray", ("box", -66, 5, z0, 66, 150, z0 + 1.5), mv)
        add(f"D{i+1}_Tray_Side_L", g, "tray", ("box", -66, 5, z0, -64.5, 150, z0 + 16), mv)
        add(f"D{i+1}_Tray_Side_R", g, "tray", ("box", 64.5, 5, z0, 66, 150, z0 + 16), mv)
        add(f"D{i+1}_Tray_Rear", g, "tray", ("box", -66, 148.5, z0, 66, 150, z0 + 16), mv)
        add(f"D{i+1}_Runner_L", g, "metal", ("box", -68, 10, z0 + 5, -66, 148, z0 + 9), mv)
        add(f"D{i+1}_Runner_R", g, "metal", ("box", 66, 10, z0 + 5, 68, 148, z0 + 9), mv)
        # rear latch (engaged by striker) + hall magnet
        add(f"D{i+1}_Latch_Hook", g, "accent", ("box", 44, 150, z0 + 6, 56, 158, z0 + 14), mv)
        add(f"D{i+1}_Hall_Magnet", g, "dark", ("cyl", 2.5, 3, (-58, 150, z0 + 10), (0, 1, 0)), mv)
        # fixed parts per level (do not move with drawer)
        add(f"Guide_Track_L_{i+1}", "Mechanism", "metal", ("box", -xi, 8, z0 + 4, -68.2, 158, z0 + 10))
        add(f"Guide_Track_R_{i+1}", "Mechanism", "metal", ("box", 68.2, 8, z0 + 4, xi, 158, z0 + 10), cut=True)
        add(f"Hall_Sensor_{i+1}", "Electronics", "dark", ("box", -62, 158, z0 + 7, -54, 160, z0 + 13))
        # ejection compression spring between tray rear and partition
        sy0 = 150 - (EXT if i == EXT_DRAWER else 0) + 0
        L = 160 - sy0
        n = max(4, int(L / 3.5))
        for k in range(n):
            add(f"D{i+1}_Eject_Spring_{k}", "Mechanism", "spring",
                ("torus", 3.5, 0.6, (-25, sy0 + (k + 0.5) * L / n, z0 + 9), (0, 1, 0)))
        if i < N_DRAWERS and i != 0:
            add(f"Tamper_Lock_{i+1}", "Housing", "brass", ("cyl", 4, 1.5, (72.5, 0, z0 + 10), (0, -1, 0)))
            add(f"Tamper_Lock_Key_{i+1}", "Housing", "dark", ("box", 72, -1.8, z0 + 7.5, 73, -1.4, z0 + 12.5))
    add("CD_Override_Pinhole", "Housing", "dark", ("cyl", 1.25, 1, (72.5, 0, 28), (0, -1, 0)))

    # ---------------- EXTENDED DRAWER #3 DETAILS ----------------
    z0 = drawer_z(EXT_DRAWER)
    g = f"Drawer_{EXT_DRAWER+1}"
    fy = -EXT          # front face Y
    add("Clamshell_Foil_Carrier", g, "foil", ("box", -55, fy + 12, z0 + 1.5, 55, fy + 127, z0 + 3.5))
    add("Carrier_Hinge_Spine", g, "metal", ("cyl", 1.5, 110, (-55, fy + 127, z0 + 4), (1, 0, 0)))
    nb = 0
    for gx in (-31, 31):
        for cx in (-9, 9):
            for ry in (30, 52, 74):
                nb += 1
                add(f"Blister_Pocket_{nb:02d}", g, "blister", ("dome", 6, (gx + cx, fy + ry, z0 + 3.5), (0, 0, 1)))
    # pill-popper lever (22 x 38), hinged at its rear, angled up
    hx, hy, hz = 47, fy + 40, z0 + FRONT_H - 2
    add("Popper_Lever_Hinge", g, "metal", ("cyl", 2, 26, (hx - 13, hy, hz), (1, 0, 0)))
    add("Popper_Lever_Arm", g, "accent", ("box", -11, -38, 0, 11, 0, 4),
        [("rot", (1, 0, 0), -12), ("move", (hx, hy, hz))])
    add("Popper_Punch_Pin", g, "metal", ("cyl", 1.5, 18, (hx, fy + 16, z0 + 4), (0, 0, 1)))
    # front lip, drop chute, catch cup, IR pair (catch cup sits under the lip)
    add("Drop_Chute", g, "shell2", ("tube", 5.5, 7, 14, (hx, fy + 16, z0 - 14), (0, 0, 1)))
    add("Catch_Cup", g, "accent", ("tube", 6.5, 8, 6, (hx, fy + 16, z0 - 20), (0, 0, 1)))
    add("Catch_Cup_Bottom", g, "accent", ("cyl", 8, 1, (hx, fy + 16, z0 - 21), (0, 0, 1)))
    for s in (-11, 11):
        add(f"IR_{'Emitter' if s < 0 else 'Receiver'}", g, "red", ("cyl", 1.5, 4, (hx + s, fy + 16, z0 - 9), (1 if s < 0 else -1, 0, 0)))

    # ---------------- STRIKER MECHANISM (rear) ----------------
    bx, by = 50.0, 180.0
    zl, zu = 55.0, 220.0
    for nm, zz in (("Lower", zl), ("Upper", zu)):
        add(f"Pulley_{nm}", "Mechanism", "metal", ("cyl", 8, 10, (bx - 5, by, zz), (1, 0, 0)))
        add(f"Pulley_{nm}_Axle", "Mechanism", "metal", ("cyl", 1.5, 24, (bx - 12, by, zz), (1, 0, 0)))
        add(f"Belt_Wrap_{nm}", "Mechanism", "belt", ("tube", 8, 9.5, 6, (bx - 3, by, zz), (1, 0, 0)))
    add("GT2_Belt_Front_Run", "Mechanism", "belt", ("box", bx - 3, by - 9.5, zl, bx + 3, by - 8, zu))
    add("GT2_Belt_Rear_Run", "Mechanism", "belt", ("box", bx - 3, by + 8, zl, bx + 3, by + 9.5, zu))
    for s in (-10, 10):
        add(f"Carriage_Guide_Rod_{'L' if s < 0 else 'R'}", "Mechanism", "metal",
            ("cyl", 2, 190, (bx + s, by - 12, 46), (0, 0, 1)))
    cz = drawer_z(EXT_DRAWER) + 10
    add("Striker_Carriage", "Mechanism", "accent", ("box", bx - 13, by - 16, cz - 9, bx + 13, by - 7, cz + 9))
    add("Striker_Wedge_45deg", "Mechanism", "red",
        ("prismx", bx - 6, bx + 6, [(by - 16, cz - 7), (by - 16, cz + 7), (by - 23, cz)]))
    add("Base_Stepper_Motor", "Mechanism", "dark", ("box", bx - 14, by - 14, 21, bx + 14, by + 14, 45))
    add("Motor_Shaft_Pulley", "Mechanism", "metal", ("cyl", 3, 8, (bx, by, 45), (0, 0, 1)))

    # ---------------- ELECTRONICS IN BASE ----------------
    add("Battery_Pack_5000mAh", "Electronics", "batt", ("box", -65, 12, 5, 65, 100, 17))
    add("Main_PCB", "Electronics", "pcb", ("box", -65, 105, 5, 65, 190, 6.6))
    for k, (cx, cy, sx, sy, hh) in enumerate([(-30, 130, 20, 20, 3), (10, 125, 14, 10, 2),
                                              (35, 160, 18, 12, 4), (-40, 170, 10, 10, 6),
                                              (55, 182, 12, 9, 4)]):
        add(f"PCB_Component_{k+1}", "Electronics", "dark",
            ("box", cx - sx / 2, cy - sy / 2, 6.6, cx + sx / 2, cy + sy / 2, 6.6 + hh))
    add("GSM_Module", "Electronics", "metal", ("box", 46, 140, 6.6, 70, 158, 9))
    return parts



# =====================================================================
#  FreeCAD builder  (Macro > Macros... > select this file > Execute)
#  Creates document "MediGuard_CarePro_C" with every part as its own
#  solid, grouped (Housing, Header, Drawer_1..8, Mechanism, Electronics,
#  Base, Ports), coloured, then saves .FCStd and exports .step next to
#  this macro (or in your home folder if that location is unknown).
# =====================================================================
CUTAWAY = False   # True = hide right wall / roof so the internals are visible

import os
import FreeCAD as App
import Part
from FreeCAD import Vector as V


def _make(p):
    k, *a = p["prim"]
    if k == "box":
        x0, y0, z0, x1, y1, z1 = a
        s = Part.makeBox(x1 - x0, y1 - y0, z1 - z0, V(x0, y0, z0))
    elif k == "cyl":
        r, h, b, d = a
        s = Part.makeCylinder(r, h, V(*b), V(*d))
    elif k == "tube":
        ri, ro, h, b, d = a
        dv = V(*d); dv.normalize()
        outer = Part.makeCylinder(ro, h, V(*b), dv)
        inner = Part.makeCylinder(ri, h + 2, V(*b) - dv * 1, dv)
        s = outer.cut(inner)
    elif k == "prismx":
        x0, x1, pts = a
        vs = [V(x0, y, z) for y, z in pts]
        vs.append(vs[0])
        s = Part.Face(Part.makePolygon(vs)).extrude(V(x1 - x0, 0, 0))
    elif k == "dome":
        r, c, d = a
        s = Part.makeSphere(r, V(*c), V(*d), 0, 90, 360)
    elif k == "rects":
        rs, z0, z1 = a
        s = Part.makeCompound([Part.makeBox(x1 - x0, y1 - y0, z1 - z0, V(x0, y0, z0)) for x0, y0, x1, y1 in rs])
    elif k == "torus":
        R, r, c, d = a
        s = Part.makeTorus(R, r, V(*c), V(*d))
    else:
        raise ValueError(k)
    for op in p["tf"]:
        if op[0] == "rot":
            s.rotate(V(0, 0, 0), V(*op[1]), op[2])
        else:
            s.translate(V(*op[1]))
    return s


def run():
    doc = App.newDocument("MediGuard_CarePro_C")
    groups, objs, fails = {}, [], []
    for p in build():
        try:
            shp = _make(p)
        except Exception as e:  # keep going if one part fails
            fails.append((p["name"], str(e)))
            continue
        g = groups.get(p["group"])
        if g is None:
            g = doc.addObject("App::DocumentObjectGroup", p["group"])
            groups[p["group"]] = g
        o = doc.addObject("Part::Feature", p["name"])
        o.Shape = shp
        g.addObject(o)
        objs.append(o)
        if App.GuiUp:
            o.ViewObject.ShapeColor = tuple(p["color"])
            if CUTAWAY and p["cut"]:
                o.ViewObject.Visibility = False
    doc.recompute()
    try:
        base = os.path.dirname(os.path.abspath(__file__))
    except NameError:
        base = os.path.expanduser("~")
    fc = os.path.join(base, "MediGuard_CarePro_C.FCStd")
    st = os.path.join(base, "MediGuard_CarePro_C.step")
    try:
        doc.saveAs(fc)
    except Exception as e:
        fails.append(("save FCStd", str(e)))
    try:
        import Import
        Import.export(objs, st)
    except Exception as e:
        fails.append(("export STEP", str(e)))
    if App.GuiUp:
        import FreeCADGui as Gui
        Gui.activeDocument().activeView().viewIsometric()
        Gui.SendMsgToActiveView("ViewFit")
    App.Console.PrintMessage(f"MediGuard: {len(objs)} parts built. Saved {fc} and {st}\n")
    for n, e in fails:
        App.Console.PrintWarning(f"  failed: {n}: {e}\n")


run()
